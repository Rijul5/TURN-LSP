module xyt6 {
    namespace 'ff';
    prefix 'sss';

    choice XXXXXXDDDDDDDDXX {
        default: 'x';
        leaf 'bar' {
            type string;
        }
        leaf 'bar1' {
            type string;
        }
        leaf 'SSSSDDS' {
            type string;
        }

    }
}
